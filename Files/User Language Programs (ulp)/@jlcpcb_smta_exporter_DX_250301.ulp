/*

Copyright 2019 OXullo Intersecans <x@brainrapers.org>

Permission is hereby granted, free of charge, to any person obtaining a copy of this software and associated documentation files (the "Software"), to deal in the Software without restriction, including without limitation the rights to use, copy, modify, merge, publish, distribute, sublicense, and/or sell copies of the Software, and to permit persons to whom the Software is furnished to do so, subject to the following conditions:

The above copyright notice and this permission notice shall be included in all copies or substantial portions of the Software.

THE SOFTWARE IS PROVIDED "AS IS", WITHOUT WARRANTY OF ANY KIND, EXPRESS OR IMPLIED, INCLUDING BUT NOT LIMITED TO THE WARRANTIES OF MERCHANTABILITY, FITNESS FOR A PARTICULAR PURPOSE AND NONINFRINGEMENT. IN NO EVENT SHALL THE AUTHORS OR COPYRIGHT HOLDERS BE LIABLE FOR ANY CLAIM, DAMAGES OR OTHER LIABILITY, WHETHER IN AN ACTION OF CONTRACT, TORT OR OTHERWISE, ARISING FROM, OUT OF OR IN CONNECTION WITH THE SOFTWARE OR THE USE OR OTHER DEALINGS IN THE SOFTWARE.

*/

// Note: This is a merge from the various ULP:

#usage "<b>JLCPCB BOM/CPL Files Generator - SMT Top and Bottom</b>\n"
	"<p>"
	"Generates BOM and CPL files for JLCPCB SMT/TH dual side assembly service"
	"https://jlcpcb.com/smt-assembly"
	"<p>"
	"Run the ULP from the board editor"
	"<p>"
	"<author>Author: OXullo Intersecans x@brainrapers.org</author>"
	"<p>"       
	"<author>JLC Updates Author: Dave Williams DitroniX 2025</author>"
	"Removed Promts to speed up ULP"
	"Included new attributes for JLC PCB."
	"Included PN_JLC and PN_JLC2."
	"Include BOM = Yes.  JLC URL. Top Only."
	"Added Filter to reject NF DNP"
	"Added Component Count. Updated Dialog"
	"ULP Reformatted"	


int layer_id_map[] = { 1, 16 };
UL_ELEMENT selected_elements[];
string layer_name_map[] = {"Top", "Bottom"};

string replace_commas(string s)
{
    while (strstr(s, ",") >= 0) {  // convert commas to spaces
        string substitution_string = " ";
        sprintf(s, "%s%s%s", strsub(s, 0, strstr(s, ",")), substitution_string, strsub(s, strstr(s, ",")+1));
    }

    return s;
}

// Dumbest implementation of fmod
real angle_mod(real angle)
{
    while (angle < 0) {
        angle += 360;
    }

    while (angle >= 360) {
        angle -= 360;
    }
    return angle;
}

// Borrowed from e-brueckenklemmenverwaltung.ulp
string strip(string s)
{
    int i, n;
    string t;

    while (s && isspace(s[0])) {
        s = strsub(s, 1);
    }

    while (s && isspace(s[strlen(s) - 1])) {
        s = strsub(s, 0, strlen(s) - 1);
    }

    for (i = 0; i < strlen(s); i++) {
        if (!isspace(s[i])) {
            t[n++] = s[i];
        } else {
            if ((strlen(s) > i+1) && isspace(s[i+1]));
            else t[n++] = s[i];
        }
    }

    s = t;

    return s;
}

string get_lcsc_part(UL_ELEMENT E)
{
    E.attributes(A) {
        if (A.name == "LCSC_PART" || A.name == "LCSC" || A.name == "PN_JLC") {
            return replace_commas(A.value);
        }
    }
    return "";
}

int is_dnp(UL_ELEMENT E)
{
    E.attributes(A) {
        if (A.value == "DNP" || A.value == "NF" || A.name == "DNP" || A.name == "DNF") {
            return 1;
        }
    }
    return 0;
}

if (board) board(B) {

        string txt;
        int layer_choice = 0;
        int skip_empty = 1;

    string output_dir = dlgDirectory("Export files to", filedir(B.name));

    if (output_dir == "") {
        exit(0);
    }

    int element_count = 0;

    // Gather the components that will appear in BOM/CPL
    B.elements(E) if (E.populate && !is_dnp(E)) {
        E.package.contacts(C) {
            if (C.smd || C.pad) {
				selected_elements[element_count++] = E;
				break;
            }
        }
    }

    string base_path = (output_dir + "/" + 
        strsub(filename(B.name), 0, strlen(filename(B.name)) - 4));

    string cpl_filename = base_path + "_cpl.csv";
    string bom_filename = base_path + "_bom.csv";

    output(cpl_filename) {
        printf("Designator,Mid X,Mid Y,Layer,Rotation\n");

        for (int i = 0 ; i < element_count ; ++i) {
                UL_ELEMENT E = selected_elements[i];
                if (skip_empty && E.value == "" || E.value == "DNP" || E.value == "NF")
                {
                    continue;
                }
                int angle = E.angle;

            string layer = "Top";
            if (E.mirror) {
                layer = "Bottom";
            }

                E.attributes(A)
                { // manually rotate the part
                    if (A.name == "JLC_ROTATION" || A.name == "JLC_ROT")
                    {
                        angle = angle + strtol(A.value);

                        while (angle > 360)
                        {
                            angle = angle - 360;
                        }
                    }
                }

                if (layer_name_map[layer_choice] == "Bottom")
                {
                    angle = (360 - angle);
                    angle = angle + 180;
                    angle = angle % 360;
                }
                real ang = angle;

            printf("%s,%5.2f,%5.2f,%s,%.1f\n",
                E.name, u2mm(E.x), u2mm(E.y),
                layer,
                angle_mod(angle));
        }
    }

        // Output CSV
        output(bom_filename)
        {
            int i;
            int indexes[];
            numeric string values[];

			for (i = 0; i < element_count; ++i)
            {
                indexes[i] = i;
                values[i] = selected_elements[i].value;
            }
            sort(element_count, indexes, values);
			
			
            printf("Comment,Designator,Footprint,LCSC Part, JLC Alternative, BOM, COUNT, JLC URL1, JLC URL2\n");

            string current_value = "";
            string current_footprint = "";
            string current_lcscpart = "";
            string designators = "";
            string current_lcscalt = "";
            string current_bom = "";
            string current_counted = "";
            string current_url1 = "";
            string current_url2 = "";
            string E_LCSC_value = "";
            string E_LCSCA_value = "";
            int notstarting = 0;
            int current_count = 0;

            for (i = 0; i < element_count; ++i)
            {
                UL_ELEMENT E = selected_elements[indexes[i]];

                if (skip_empty && E.value == "" || E.value == "DNP" || E.value == "NF")
                {

                    continue;
                }

                // get LCSC_PART value of a part
                E.attributes(A)
                {
                    if (A.name == "LCSC_PART" || A.name == "LCSC" || A.name == "PN_JLC")
                    {
                        E_LCSC_value = replace_commas(A.value);
                        current_url1 = "https://jlcpcb.com/partdetail/" + current_lcscpart;
                        current_url2 = "https://jlcpcb.com/partdetail/" + current_lcscalt;
                    }
                    else
                    {
                        E_LCSC_value = "";
                        current_url1 = "";
                        current_url2 = "";
                    }
                }

                // get LCSC_ALT value of a part
                E.attributes(A)
                {
                    if (A.name == "PN_JLC2")
                    {
                        E_LCSCA_value = replace_commas(A.value);
                    }
                    else
                    {
                        E_LCSCA_value = "";
                    }
                }

                // get BOMvalue of a part
                E.attributes(A)
                {
                    if (A.name == "BOM")
                    {
                        current_bom = replace_commas(A.value);
                    }
                }

                if (current_lcscpart != "")
                {
                    current_url1 = "https://jlcpcb.com/partdetail/" + current_lcscpart;
                }
                
                if (current_lcscalt != "")
                {
                    current_url2 = "https://jlcpcb.com/partdetail/" + current_lcscalt;
                }                   

                if (notstarting && (E.value != current_value && E_LCSC_value != current_lcscpart))
                {
                    sprintf(current_counted, "%d", current_count);
                    printf("%s,%s,%s,%s,%s,%s,%s,%s,%s\n", current_value, designators, current_footprint, current_lcscpart, current_lcscalt, current_bom, current_counted, current_url1, current_url2);
                    designators = "";
                    current_count = 0;
                }

                current_count++;

                notstarting = 1;

                if (designators != "")
                {
                    designators += " ";
                }
                designators += E.name;
                current_value = replace_commas(E.value);
                current_footprint = replace_commas(E.package.name);
                current_lcscpart = "";
                current_lcscalt = "";
                current_bom = "";
                current_url1 = "";

                // get LCSC_PART value of a part
                E.attributes(A)
                {
                    if (A.name == "LCSC_PART" || A.name == "LCSC" || A.name == "PN_JLC")
                    {
                        current_lcscpart = replace_commas(A.value);
                    }
                }

                // get BOMvalue of a part
                E.attributes(A)
                {
                    if (A.name == "BOM")
                    {
                        current_bom = replace_commas(A.value);
                    }
                }

                // get JLC_ALT_PART value of a part
                E.attributes(A)
                {
                    if (A.name == "PN_JLC2")
                    {
                        current_lcscalt = replace_commas(A.value);
                    }
                }

                if (current_lcscpart != "")
                {
                    current_url1 = "https://jlcpcb.com/partdetail/" + current_lcscpart;
                }
                
                if (current_lcscalt != "")
                {
                    current_url2 = "https://jlcpcb.com/partdetail/" + current_lcscalt;
                }                
            }

            if (current_value != "")
            {
                sprintf(current_counted, "%d", current_count);
                printf("%s,%s,%s,%s,%s,%s,%s,%s,%s\n", current_value, designators, current_footprint, current_lcscpart, current_lcscalt, current_bom, current_counted, current_url1, current_url2);
            }
        }
    }
else
{
    dlgMessageBox("Run this ULP from a Board", "OK");
    exit(0);
}
